Module DEFINITIONS ::= 
BEGIN 

Message ::= SEQUENCE 
{ 
	msgType MsgType,
	number INTEGER,
	string IA5String
}   
MsgType ::= ENUMERATED
{
	clientToServerInt (0),
	serverToClientAnswer (1),
	clientToServerString (2),
	serverToClientResult (3)
}

END
